FME workspace generate_required_fields_for_osmconf.fmw

Parameters:
- OSM_MA_Config_XLS = C:\Users\zool1301\Documents\MapAction\Code\osm2mapaction\config_files\OSM_to_MA_ascii_v6.xls   # XLS file containing the osm_ma_xwalk named range
- OSMCONF_TEMPLATE = C:\Users\zool1301\Documents\MapAction\Code\osm2mapaction\config_files\osmconf.template.txt   # Template OSMCONF text file
- OutputFolder = $(FME_MF_DIR_USERTYPED)\..\config_files   # Where should the output osmconf_mapaction.ini file be written

Readers:
- XLSXR_1: XLSXR from $(OSM_MA_Config_XLS)
- TEXTLINE_1: TEXTLINE from $(OSMCONF_TEMPLATE)

Note: Read the named range
osm_ma_xwalk (reader XLSXR_1)
    attributes: OSM_tag_name char(20), OSM_tag_value char(165), Element_icon char(36), Comment char(519), Useful_for_MapAction char(2), Data Category description char(29), Cat_value char(5), Date Theme description char(73), Theme_value char(4), Conforms_to_MA_Hierarchy char(5), OSM_Element char(24), Data type char(14), pt char(3), ln char(3), py char(3), rel char(4)
    -> AttributeKeeper
AttributeKeeper
    KEEP_ATTRS = OSM_tag_name,OSM_tag_value,Useful_for_MapAction,Data type
    -> Tester
Tester
    TEST_DESCRIPTION = ""
    TEST_CLAUSE = TEST @Value(Useful_for_MapAction) = Y
    BOOL_OP = OR
    TEST_MODE = Automatic
    PASSED -> AttributeSplitter
Note: Convert to one feature per OSM tag and per geometry type
AttributeSplitter
    ATTR_NAME = Data type
    DELIMITER = " "
    DROP_EMPTY_PARTS = No
    LIST_NAME = _dataTypes
    TRIM_OPTION = Both
    -> ListExploder
ListExploder
    LIST_ATTR = _dataTypes{}
    ATTR_ACCUM_MODE = Merge Incoming List
    ATTR_CONFLICT_RES = Use Original
    INDEX_ATTR = _element_index
    LIST_FOUND -> AttributeKeeper_2
AttributeKeeper_2
    KEEP_ATTRS = _dataTypes,OSM_tag_name
    -> Tester_2
Tester_2
    TEST_DESCRIPTION = ""
    TEST_CLAUSE:
      TEST @Value(_dataTypes) = pt
      TEST @Value(_dataTypes) = py
      TEST @Value(_dataTypes) = ln
    BOOL_OP = OR
    TEST_MODE = Automatic
    PASSED -> DuplicateRemover
DuplicateRemover
    KEYATTR = _dataTypes OSM_tag_name
    UNIQUE -> AttributeTrimmer
Note: This is a basic workbench to create the osmconf.ini file necessary to make OGR expose the OSM attributes required by the osm2ma code. / It basically just concatenates the content of the relevant bit of the excel config file, and then substitutes this in to a template osmconf.ini file.It only needs to be re-run if the excel file changes.
AttributeTrimmer
    TRIM_TO_NONE = Yes
    TRIM_TYPE = Both
    SRC_ATTRS = OSM_tag_name
    -> ListBuilder
Note: Convert to one feature per geometry type, with the required OSM attributes for each as a comma-separated string
ListBuilder
    GRP_BY = _dataTypes
    LIST_NAME = _list
    -> ListConcatenator
ListConcatenator
    LIST_ATTR = _list{}.OSM_tag_name
    VAL_ATTR = _concatenated
    DROP_EMPTY_PARTS = No
    SEP = ,
    -> AttributeValueMapper
Note: Replace the text "pt" / "ln" / "py" with somthing less likely to be in the template text file
AttributeValueMapper
    VAL_ATTR = OSM_Template_SearchReplaceText
    LUT = pt,_Point_Attributes_XYZ_,ln,_Line_Attributes_XYZ_,py,_Polygon_Attributes_XYZ_
    SRC = _dataTypes
    DIRECTION = Forward (Source To Destination)
    -> AttributeKeeper_3
Note: Rename the concatenated attribute to a name that varies according to the value of the type attribute
AttributeKeeper_3
    KEEP_ATTRS = _concatenated,OSM_Template_SearchReplaceText
    -> BulkAttributeRenamer
BulkAttributeRenamer
    ATTRCHOICE = All Attributes
    PATTERN_ACTION_DISP = String Replace
    REPLACE_STR = @Value(OSM_Template_SearchReplaceText)
    REPLACE_PATTERN = _concatenated
    CASE_DISP = yes
    -> AttributeExposer
AttributeExposer
    ATTR_LIST = _Point_Attributes_XYZ_,_Line_Attributes_XYZ_,_Polygon_Attributes_XYZ_
    -> UnconditionalFeatureMerger [input 2]
Note: Read the template file as a single feature attribute (not split by line)
text_line (reader TEXTLINE_1)
    attributes: text_line_data buffer
    -> UnconditionalFeatureMerger [input 1]
Note: Attach the three concatenated attributes to the template text file feature
UnconditionalFeatureMerger
    PROCESS_DUPS = Yes
    Merged -> StringReplacer
Note: Perform the string replacements
StringReplacer
    FIND_TEXT = {MAPACTION_POINT_ATTRIBUTES}
    REPLACE_TEXT = @Value(_Point_Attributes_XYZ_)
    REGEXP = no
    NO_MATCH = _FME_NO_OP_
    CASE = no
    SRC_ATTRS = text_line_data
    -> StringReplacer_2
StringReplacer_2
    FIND_TEXT = {MAPACTION_LINE_ATTRIBUTES}
    REPLACE_TEXT = @Value(_Line_Attributes_XYZ_)
    REGEXP = no
    NO_MATCH = _FME_NO_OP_
    CASE = no
    SRC_ATTRS = text_line_data
    -> StringReplacer_3
StringReplacer_3
    FIND_TEXT = {MAPACTION_POLYGON_ATTRIBUTES}
    REPLACE_TEXT = @Value(_Polygon_Attributes_XYZ_)
    REGEXP = no
    NO_MATCH = _FME_NO_OP_
    CASE = no
    SRC_ATTRS = text_line_data
    -> AttributeCreator
AttributeCreator
    ATTR_LIST = _outputFile,$(OutputFolder)\osmconf_mapaction.ini
    -> StringReplacer_3_Output
    -> AttributeFileWriter
AttributeFileWriter
    SOURCE_ATTR = text_line_data
    CHAR_ENCODING = fme-system
    FILE_NAME = @Value(_outputFile)
    OVERWRITE_FILE = Overwrite file
StringReplacer_3_Output: Inspector

FME custom transformer UnconditionalFeatureMerger
This transformer is a wrapper around the FeatureMerger, configuring it to merge all incoming requestors with supplier attributes. Optionally, it can be configured to process duplicate suppliers.
Please note that the UncoditionalFeatureMerger may be deprecated in the near future, as the FeatureMerger now allows unconditional merging via constant values for the join.
Input ports:
    Requestor
Receives the new attributes/geometry from the features connected to the Supplier port.
    Supplier
The source of new attributes/geometry for features that enter through the Requestor port. If Process Duplicate suppliers is off, only the first Supplier will be used.
    Output ports:
    Merged
Requestors that find a Supplier. In the case of unconditional merging, this should be all Requestors.
    Referenced
Suppliers that are found by at least one Requestor.
    Note: A Supplier may still be output through this port even though none of its attributes were merged. This can occur because all of the attributes were already present in the Requestor or were provided by earlier Suppliers.
    DuplicateSupplier
Extra Supplier features. Note that duplicate Suppliers will only be output if Process Duplicate Suppliers is set to No. If Process Duplicate Suppliers is set to Yes, then duplicate Suppliers will be output via the Referenced port.
Copyright (c) 2014 Safe Software Inc. 
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- PROCESS_DUPS = No   # Process Duplicate Suppliers

Requestor (input)
    -> FeatureMerger [input 1]
Supplier (input)
    -> FeatureMerger [input 2]
FeatureMerger
    SUPPLIERS_FIRST = No
    PROCESS_DUPS = $(PROCESS_DUPS)
    SUPPLIER_PREFIX_DUMMY = YES
    IGNORE_NULLS = Yes
    JOIN_KEYS = 1 1 AUTO
    MERGE_TYPE = Attributes Only
    GEOM_TYPE = Build Polygons
    MERGED -> Merged (output)
    REFERENCED -> Referenced (output)
    DUPLICATE_SUPPLIER -> DuplicateSupplier (output)
Merged (output)
Referenced (output)
DuplicateSupplier (output)
