FME workspace OSM2MapAction.fmw
Title: OSM2MapAction
Description: This workbench provides the same functionality as the OSM2MA Python scripts. It reads the MapAction OSM Excel config file, and OSM data, and outputs MapAction DNC-compliant shapefiles.
It was created to "ground truth" results from the python tools, but in fact it may well be useful in its own right.
Usage: The only limitation with using this workbench is that FME cannot read OSM .PBF format data. Instead the workbench has been written to read OSM data that have been converted from the PBF format into an intermediate temporary SQLite database.
This can be done at the command line with a single command:
    ogr2ogr -f SQLite tempSQLits.sl3 osm-input-file.pbf
You will first need to have set up the mapaction-specific osmconf.ini file (or point to it in the above command). The command will generate an output sqlite file containing one table for each geometry type. Be aware that the database will probably be several times the size of the PBF file.
Then simply run the workbench specifying the path to this database, and the output directory, and the other clauses for the DNC names of the shapefiles.

Parameters:
- MapactionOSMDNCMapping = C:\Users\zool1301\Documents\MapAction\Code\osm2mapaction\config_files\OSM_to_MA_ascii_v6.xls   # Excel file mapping OSM tags to Mapaction DNC
- GEOEXT_CLAUSE = pry   # GeoExtent Clause (for shp name)
- SCALE_CLAUSE = s1   # Scale Clause (for shp name)
- ShapeDir_Root = C:\Temp\MA_OSM_Test\test_fme_full_pry_sqlite   # Top directory within which to create shapefiles
- SourceDataset_Spatialite = $(FME_MF_DIR)tempSQLite.sl3   # Spatialite file containing PBF translated with OGR2OGR
- SHAPE_OUT_COMPRESSED_SHAPE_FILE_SHAPE = No   # Create Compressed (Zipped) Shape File (.shz)
- shpNameTemplate = {geo_extd}_{cat}_{thm}_{geom_type}_{scale}_osm_pp   # Shapefile Name Template

Readers:
- XLSXR_1: XLSXR from $(MapactionOSMDNCMapping)
- SCHEMA_1: SCHEMA from $(SourceDataset_Spatialite)

Writers:
- SHAPE_1: SHAPE to $(ShapeDir_Root) in EPSG:4326

Note: This workbench provides the functionality of the OSM2MA Python tools. It reads the Excel configuration spreadsheet to get the definition of the output MapAction DNC shapefiles, and it reads the OSM data and translates the appropriate features into output shapefiles with the correct names and attributes. / Note that the major exception is that FME cannot read OSM PBF files. This workbench has instead been written to read from an SQLite database. The .PBF must first be translated into SQLite. This can be done with the OGR2OGR tool via the following command: / ogr2ogr -f SQLite tempSQLits.sl3 osm-input-file.pbf / (assuming that you have the mapaction osmconf.ini file set up). This will create one table in the DB for each geometry type, and each will have all the attributes specified in the osmconf.ini file / Another workbench RunOSM2MapAction.fmw has been created to do this for you. Open and run that workbench instead of this one - it will trigger this workbench after the translation is complete!
Note: Decide the format for this SQL clause
TestFilter
    DEFAULT_VALUE = SpecificValue
    TEST_LIST:
      BOOL_OP,OR,COMPOSITE_TEST,<Unused>,TEST_CLAUSE,"TEST @LowerCase(@Trim(@Value(OSM_tag_value))) = *
      TEST @LowerCase(@Trim(@Value(OSM_tag_value))) = user defined
      TEST @LowerCase(@Trim(@Value(OSM_tag_value))) = number
      TEST @LowerCase(@Trim(@Value(OSM_tag_value))) = url or article title",SelectAsNotNull,BOOL_OP,OR,COMPOSITE_TEST,<Unused>,TEST_CLAUSE,"TEST @Value(OSM_tag_value) CONTAINS /",ValueListSlash,BOOL_OP,OR,COMPOSITE_TEST,<Unused>,TEST_CLAUSE,"TEST @Value(OSM_tag_value) CONTAINS ,",ValueListComma,BOOL_OP,OR,COMPOSITE_TEST,<Unused>,TEST_CLAUSE,"TEST @Value(OSM_tag_value) = FakeValueThatNeverOccurs1234~#",NameFieldDoNotIncludeInSelect
    SelectAsNotNull -> AttributeCreator_2
    SpecificValue -> AttributeCreator
    ValueListSlash -> AttributeSplitter_2
    ValueListComma -> AttributeSplitter_3
    NameFieldDoNotIncludeInSelect -> AttributeExposer
Note: Use X IS NOT NULL syntax
AttributeCreator_2
    ATTR_LIST = _UniqueClause,@Value(_sanitisedColName) IS NOT null
    -> AttributeExposer
Note: Values separated by slash, split, trim whitespace, and reconcatenate with comma
AttributeSplitter_2
    LIST_NAME = _values
    ATTR_NAME = OSM_tag_value
    TRIM_OPTION = Both
    DROP_EMPTY_PARTS = No
    DELIMITER = /
    -> ListExploder_3
Note: Values separated by comma (e.g. voltages), split anyway to trim whitespace then reconcatentate
AttributeSplitter_3
    LIST_NAME = _values
    ATTR_NAME = OSM_tag_value
    TRIM_OPTION = Both
    DROP_EMPTY_PARTS = No
    DELIMITER = ,
    -> ListExploder_3
Note: We need to quote each value before re-concatentating so we end up with e.g. ('Yes','No') not (Yes,No). / Split to individual features, quote and trim, recombine.
ListExploder_3
    INDEX_ATTR = _element_index
    LIST_ATTR = _values{}
    ATTR_CONFLICT_RES = Use Original
    ATTR_ACCUM_MODE = Merge Incoming List
    LIST_FOUND -> AttributeCreator_7
AttributeCreator_7
    ATTR_LIST = _values,'@Trim(@Value(_values))'
    -> ListBuilder_2
ListBuilder_2
    LIST_NAME = _list
    GRP_BY = _geomTable _sanitisedColName _shpName Cat_value fme_data_type name OSM_tag_name OSM_tag_value
    -> AttributeRemover_3
AttributeRemover_3
    LIST_ATTRS = _list{}._element_index _list{}._geomTable _list{}._sanitisedColName _list{}._shpName _list{}.Cat_value _list{}.fme_data_type _list{}.name _list{}.OSM_tag_name _list{}.OSM_tag_value
    -> ListConcatenator
ListConcatenator
    SEP = ,
    LIST_ATTR = _list{}._values
    DROP_EMPTY_PARTS = No
    VAL_ATTR = _concatenatedValueSet
    -> AttributeCreator_6
Note: Use X IN (A,B,C) syntax
AttributeCreator_6
    ATTR_LIST = _UniqueClause,@Value(_sanitisedColName) IN (@Value(_concatenatedValueSet))
    -> AttributeExposer
Note: A specific value, just trim whitespace and use X=Y syntax
AttributeCreator
    ATTR_LIST = _UniqueClause,@Value(_sanitisedColName)='@Trim(@Value(OSM_tag_value))'
    -> AttributeExposer
AttributeExposer
    ATTR_LIST = fme_basename,fme_coordinate_system,fme_dataset,fme_feature_type,fme_format_long_name,fme_format_short_name,fme_geometry{}
    -> AttributeKeeper_2
AttributeKeeper_2
    KEEP_ATTRS = _geomTable,_shpName,_UniqueClause,fme_data_type,name,Cat_value
    -> DuplicateRemover
    -> FeatureMerger [input 1]

Bookmark: Parse the excel config file to generate the shapefile name and associated info for each row (tag/value pair)
Note: Read the relevant named range from the Excel sheet
osm_ma_xwalk/xwalk (reader XLSXR_1)
    attributes: OSM_tag_name char(20), OSM_tag_value char(165), Element_icon  char(36), Comment  char(519), Useful_for_MapAction char(2), Data Category description char(29), Cat_value char(5), Date Theme description char(73), Theme_value char(4), Conforms_to_MA_Hierarchy char(5), OSM_Element  char(24), Data type char(14), pt char(3), ln char(3), py char(3), rel char(4)
    -> Tester_2
Note: Only keep "useful" rows
Tester_2
    TEST_CLAUSE = TEST @Value(Useful_for_MapAction) = Y
    BOOL_OP = OR
    TEST_MODE = Automatic
    TEST_DESCRIPTION = ""
    PASSED -> AttributeSplitter
Note: Work with the single geometry types column; split it so we get one feature for each geometry type given in the column
AttributeSplitter
    LIST_NAME = _geomTypes
    ATTR_NAME = Data type
    TRIM_OPTION = Both
    DROP_EMPTY_PARTS = Yes
    DELIMITER = " "
    -> ListExploder
ListExploder
    INDEX_ATTR = _element_index
    LIST_ATTR = _geomTypes{}
    ATTR_CONFLICT_RES = Use Original
    ATTR_ACCUM_MODE = Merge Incoming List
    LIST_FOUND -> AttributeRenamer
AttributeRenamer
    ATTR_LIST = _geomTypes,_OneGeomType,
    -> ParameterFetcher
Note: Build the DNC-compliant shapefile name that features selected by this Excel row will be written to
ParameterFetcher
    ATTR_LIST = _shpName {$(shpNameTemplate)} _GEOEXT_CLAUSE {$(GEOEXT_CLAUSE)} _SCALE_CLAUSE {$(SCALE_CLAUSE)}
    -> StringReplacer
StringReplacer
    SRC_ATTRS = _shpName
    NO_MATCH = _FME_NO_OP_
    REPLACE_TEXT = @Value(Cat_value)
    CASE = no
    REGEXP = no
    FIND_TEXT = {cat}
    -> StringReplacer_2
StringReplacer_2
    SRC_ATTRS = _shpName
    NO_MATCH = _FME_NO_OP_
    REPLACE_TEXT = @Value(Theme_value)
    CASE = no
    REGEXP = no
    FIND_TEXT = {thm}
    -> StringReplacer_3
StringReplacer_3
    SRC_ATTRS = _shpName
    NO_MATCH = _FME_NO_OP_
    REPLACE_TEXT = @Value(_OneGeomType)
    CASE = no
    REGEXP = no
    FIND_TEXT = {geom_type}
    -> StringReplacer_4
StringReplacer_4
    SRC_ATTRS = _shpName
    NO_MATCH = _FME_NO_OP_
    REPLACE_TEXT = @Value(_GEOEXT_CLAUSE)
    CASE = no
    REGEXP = no
    FIND_TEXT = {geo_extd}
    -> StringReplacer_5
StringReplacer_5
    SRC_ATTRS = _shpName
    NO_MATCH = _FME_NO_OP_
    REPLACE_TEXT = @Value(_SCALE_CLAUSE)
    CASE = no
    REGEXP = no
    FIND_TEXT = {scale}
    -> AttributeKeeper
AttributeKeeper
    KEEP_ATTRS = _OneGeomType,_shpName,Cat_value,OSM_tag_name,OSM_tag_value
    -> AttributeValueMapper
Note: Replace "py" etc with the name of the generic database table created by ogr2ogr e.g. multipolygons
AttributeValueMapper
    SRC = _OneGeomType
    LUT = pt,points,ln,lines,py,multipolygons
    DIRECTION = Forward (Source To Destination)
    VAL_ATTR = _geomTable
    -> StringReplacer_7
Note: The osmconf.ini file is set to launder names by replacing ':' with '_' so first update what we're looking for to reflect that
StringReplacer_7
    SRC_ATTRS = OSM_tag_name
    NO_MATCH = _FME_NO_OP_
    REPLACE_TEXT = _
    CASE = no
    REGEXP = no
    FIND_TEXT = :
    -> FeatureMerger_3 [input 1]
    -> AttributeCreator_8
Note: Also let's request the "name" field each time so our shapefiles are a bit more useful
AttributeCreator_8
    ATTR_LIST = OSM_tag_name,name,OSM_tag_value,FakeValueThatNeverOccurs1234~#
    -> FeatureMerger_3 [input 1]

Bookmark: Check required columns are available
Note: Read the schema of the OSM generic tables, to ensure that the attribute we will be asking for in the SQL clause actually exists., It should do, but in fact if there were no features with a given attribute or tag then it may not have been created by ogr2ogr. / This also provides the info necessary for the shapefile writers to add the relevant attributes to the output shps.
schema (reader SCHEMA_1)
    attributes: fme_feature_type_name varchar(200)
    -> ListExploder_2
Note: Get one feature for each attribute that is present in the OSM tables, i.e. a normalised view of the table schemas
ListExploder_2
    INDEX_ATTR = _element_index
    LIST_ATTR = attribute{}
    ATTR_CONFLICT_RES = Use Original
    ATTR_ACCUM_MODE = Merge Incoming List
    LIST_FOUND -> AttributeKeeper_4
AttributeKeeper_4
    KEEP_ATTRS = fme_data_type,name,fme_feature_type_name
    -> AvailableColumnsInData
    -> FeatureMerger_3 [input 2]
Note: For each row from the Excel sheet, ensure it corresponds to an OSM attribute that is actually present in the table - otherwise the SQL clause would be invalid and would generate an error
FeatureMerger_3
    PROCESS_DUPS = No
    ATTR_ACCUM_MODE = Merge Supplier
    JOIN_KEYS = @Value(OSM_tag_name) @Value(name) AUTO @Value(_geomTable) @Value(fme_feature_type_name) AUTO
    ATTR_CONFLICT_RES = Use Supplier
    IGNORE_NULLS = No
    MERGE_TYPE = Attributes Only
    SUPPLIERS_FIRST = No
    NOT_MERGED -> OSM_Tag_Attrib_Not_Avail_In_Data
    MERGED -> AttributeRemover
AttributeRemover
    REMOVE_ATTRS = _OneGeomType,fme_feature_type_name
    -> Tester_3
Note: Allow user to view dropped ones
OSM_Tag_Attrib_Not_Avail_In_Data: Inspector
AvailableColumnsInData: Inspector

Bookmark: Sanitise names
Note: Now any that do contain '_' (which isn't limited to those we replaced from ':' at the start), or a space, need to be qualified in the SQL for SQLite to pick them up properly
Tester_3
    TEST_CLAUSE:
      TEST @Value(OSM_tag_name) CONTAINS _
      TEST @Value(OSM_tag_name) CONTAINS
    BOOL_OP = OR
    TEST_MODE = Automatic
    TEST_DESCRIPTION = ""
    PASSED -> AttributeCreator_3
    FAILED -> AttributeCreator_4
AttributeCreator_3
    ATTR_LIST = _sanitisedColName,@Value(_geomTable).`@Value(name)`
    -> TestFilter
AttributeCreator_4
    ATTR_LIST = _sanitisedColName,@Value(name)
    -> TestFilter

Bookmark: Calculate the output column widths
Note: We want to tell the writer how wide each output column should be so we don't make a larger .dbf than necessary. Only check length once for each source attribute and base it on the whole table (rather than just the features that will be selected into this shapefile). Just a bit more efficient, but this does mean the attribs might be longer than in the Python version which uses the features actually written to each shapefile.
DuplicateRemover
    KEYATTR = _geomTable name
    UNIQUE -> AttributeKeeper_3
AttributeKeeper_3
    KEEP_ATTRS = _geomTable,name
    -> AttributeCreator_9
AttributeCreator_9
    ATTR_LIST = _GetLengthSQL,SELECT max(length(@Value(_geomTable).'@Value(name)')) len FROM @Value(_geomTable)
    -> SQLExecutor_2
Note: Ask the DB what's the max length value found in this column
SQLExecutor_2
    SQL_STATEMENT = @Value(_GetLengthSQL)
    COMBINE_ATTRS = Keep Initiator Attributes if Conflict
    EXPOSED_ATTRIBUTE_LIST = len
    COMBINE_GEOM = Result Geometry Only
    SPATIALITE_QUERY_FEATURE_TYPES_FOR_MERGE_FILTERS = Yes
    SPATIALITE_DATASET = $(SourceDataset_Spatialite)
    FORMAT = SPATIALITE
    DATASET = $(SourceDataset_Spatialite)
    RESULT -> AttributeRemover_5
AttributeRemover_5
    REMOVE_ATTRS = _GetLengthSQL
    -> FeatureMerger [input 2]
FeatureMerger
    PROCESS_DUPS = No
    ATTR_ACCUM_MODE = Merge Supplier
    JOIN_KEYS = @Value(_geomTable) @Value(_geomTable) AUTO @Value(name) @Value(name) AUTO
    ATTR_CONFLICT_RES = Use Requestor
    IGNORE_NULLS = No
    MERGE_TYPE = Attributes Only
    SUPPLIERS_FIRST = No
    MERGED -> AttributeCreator_10
AttributeCreator_10
    ATTR_LIST = fme_data_type,"FME_CONDITIONAL:DEFAULT_VALUE'fme_varchar(10)'BOOL_OP;OR;COMPOSITE_TEST;<Unused>;TEST @Value(len) MATCHES_REGEX [0-9]+'fme_varchar(@Value(len))'FME_NUM_CONDITIONS2___"
    -> ListBuilder

Bookmark: Prepare shapefile SELECT query
Note: Build the SELECT clause for each shapefile. Also construct a list of the attributes that are within it. / Each feature here contains a "name" which is the attribute name to go through, and a "uniqueclause" which is the SQL to select features when they have something relevant in that attribute
Note: Convert features into one per shapefile, with all the unique clauses on a list
ListBuilder
    LIST_NAME = _WhereClauseList
    GRP_BY = _geomTable _shpName Cat_value
    -> ListConcatenator_2
Note: Concatenate that list into a single string where clause for this shapefile
ListConcatenator_2
    SEP = " or "
    LIST_ATTR = _WhereClauseList{}._UniqueClause
    DROP_EMPTY_PARTS = Yes
    VAL_ATTR = _SelectList
    -> StringReplacer_6
Note: Sanitise - remove : in the attrib names (actually this was already done)
StringReplacer_6
    SRC_ATTRS = _SelectList
    NO_MATCH = _FME_NO_OP_
    REPLACE_TEXT = _
    CASE = no
    REGEXP = no
    FIND_TEXT = :
    -> AttributeRemover_2
Note: We will now use the other part of the list (the attribute names) as the actual instructions for the writer to tell it what columns the shapefile should have. Get rid of stuff that is on the list but not needed for that purpose.
AttributeRemover_2
    LIST_ATTRS = _WhereClauseList{}.Cat_value _WhereClauseList{}._UniqueClause _WhereClauseList{}._geomTable _WhereClauseList{}._shpName _WhereClauseList{}.len
    -> ListRenamer
ListRenamer
    LIST_COMPONENT_NAMES = _WhereClauseList{},attribute{}
    LIST_NAME = _WhereClauseList{}
    LIST_ACTION = Rename
    LEAVE_ORIG = No
    -> ListDuplicateRemover
Note: Each feature is now everything needed to read data for a single shapefile and funnel it straight through to the output shapefile.
ListDuplicateRemover
    SRC_LIST = attribute{}.name
    -> FinalFeatureSelectors
    -> FeatureReader
FinalFeatureSelectors: Inspector

Bookmark: Read the actual OSM data for each shapefile
Note: Now we have one feature for each required output shapefile. Each feature contains the shapefile name, the shapefile DNC category, the table it should be sourced from (points / lines / polygons), the WHERE clause for it, and the list of the attributes in the format necessary for the dynamic writer. / All that's left is to read the relevant features from the DB and write them out to the appropriate shapefile.
Note: FME issues reading the DB: / - Spatialite reader in FeatureReader only returns features more or less at random! / - Spatialite reader in SQLExecutor works but doesn't allow declaration of encoding, so we have to explciitly re-encode to utf8 which is v slow / - SQLite reader in FeatureReader works doesn't allow declaration of encoding, however it seems to pick it up correctly! We have to parse the geometry manually.
FeatureReader
    SQLITE3_QUERY_FEATURE_TYPES_FOR_MERGE_FILTERS = Yes
    COMBINE_GEOM = Use Result
    ATTRIBUTES = geometry_columns,"f_table_name,f_geometry_column,geometry_type,coord_dimension,srid,geometry_format",lines,"OGC_FID,GEOMETRY,osm_id,aerialway,aeroway,amenity,barrier,border_type,boundary,highway,sidewalk,ford,ice_road,incline,junction,lanes,lit,motorroad,overtaking,passing_places,surface,tracktype,traffic_calming,trail_visibility,winter_road,leisure,man_made,natural,place_numbers,postal_code,reference_point,is_in,power,cables,circuits,tunnel,voltage,wires,public_transport,railway,bridge,cutting,embankment,usage,route,sport,tourism,waterway,intermittent,lock,mooring,service,addr_interpolation,addr_inclusion,attribution,description,email,fax,fixme,image,note,phone,source,source_name,source_ref,source_ref2,url,website,wikipedia,name,name_<lg>,alt_name,alt_name_<lg>,int_name,loc_name,nat_name,official_name,old_name,old_name_<lg>,reg_name,short_name,sorting_name,covered,disused,end_date,est_width,layer,narrow,opening_hours,operator,start_date,tmc_locationcode,width,iata,icao,int_ref,lcn_ref,loc_ref,nat_ref,ncn_ref,old_ref,rcn_ref,ref,reg_ref,access,agricultural,atv,bdouble,bicycle,boat,emergency,foot,forestry,goods,hazmat,hgv,lhv,motorboat,motorcar,motor_vehicle,motorcycle,psv,roadtrain,tank,vehicle,4wd_only,maxheight,maxlength,maxspeed,maxweight,maxwidth,noexit,oneway,other_tags",multilinestrings,"OGC_FID,GEOMETRY,osm_id,name,type,other_tags",multipolygons,"OGC_FID,GEOMETRY,osm_id,osm_way_id,aerialway,aeroway,amenity,barrier,boundary,border_type,admin_level,building,height,building_levels,building_fireproof,craft,emergency,highway,lit,landuse,leisure,man_made,military,natural,office,place,population,name,place_numbers,postal_code,reference_point,is_in,power,public_transport,""public transport"",railway,route,shop,sport,tourism,waterway,addr_housenumber,addr_housename,addr_street,addr_place,addr_postcode,addr_city,addr_country,addr_full,addr_hamlet,addr_suburb,addr_subdistrict,addr_district,addr_province,addr_state,attribution,description,email,fax,fixme,image,note,phone,source,source_name,source_ref,source_ref2,url,website,wikipedia,name_<lg>,alt_name,alt_name_<lg>,int_name,loc_name,nat_name,official_name,old_name,old_name_<lg>,reg_name,short_name,sorting_name,area,covered,disused,drive_in,ele,internet_access,opening_hours,operator,start_date,wood,iata,icao,int_ref,loc_ref,nat_ref,old_ref,ref,reg_ref,bdouble,roadtrain,tank,other_tags",other_relations,"OGC_FID,GEOMETRY,osm_id,name,type,other_tags",points,"OGC_FID,GEOMETRY,osm_id,aerialway,aeroway,amenity,barrier,boundary,building,entrance,height,building_levels,building_fireproof,craft,emergency,ford,incline,lit,motorroad,mountain_pass,traffic_calming,highway,landuse,leisure,man_made,military,natural,office,place,population,name,place_numbers,postal_code,reference_point,is_in,power,public_transport,""public transport"",railway,route,shop,sport,tourism,waterway,lock,tunnel,addr_housenumber,addr_housename,addr_street,addr_place,addr_postcode,addr_city,addr_country,addr_full,addr_hamlet,addr_suburb,addr_subdistrict,addr_district,addr_province,addr_state,attribution,description,email,fax,fixme,image,note,phone,source,source_name,source_ref,source_ref2,url,website,wikipedia,name_<lg>,alt_name,alt_name_<lg>,int_name,loc_name,nat_name,official_name,old_name,old_name_<lg>,reg_name,short_name,sorting_name,bridge,covered,crossing,disused,drive_in,ele,internet_access,opening_hours,operator,start_date,tmc_locationcode,wood,iata,icao,int_ref,loc_ref,nat_ref,old_ref,ref,reg_ref,charge,toll,traffic_sign,other_tags",spatial_ref_sys,"srid,auth_name,auth_srid,srtext"
    ATTR_CONFLICT_RES = Use Result
    FORMAT = SQLITE3
    DATASET = $(SourceDataset_Spatialite)
    FEATURETYPES = @Value(_geomTable)
    WHERE = @Value(_SelectList)
    OUTPUT_FEATURES_DISPLAY = Schema and Data Features
    ATTR_ACCUM_MODE = Merge Initiator and Result
    <OTHER> -> AttributeExposer_3
AttributeExposer_3
    ATTR_LIST = GEOMETRY
    -> GeometryReplacer
GeometryReplacer
    REMOVE_ATTRIBUTE = Yes
    SOURCE = @Value(GEOMETRY)
    KIND_LONG = OGC Well Known Binary
    -> AttributeExposer_2
AttributeExposer_2
    ATTR_LIST = fme_feature_type
    -> AttributeRemover_4
AttributeRemover_4
    REMOVE_ATTRS = fme_feature_type
    -> GeometryFilter

Bookmark: Write the data to the output shapefiles
Note: Shapefile writers are dynamic in every respect except geometry type. So we need one feature type for each geometry type.
GeometryFilter
    GEOM_PORT_NAMES = Point Line Arc Area
    BREAK_AGG = No
    AREA -> File10000 (writer SHAPE_1)
    POINT -> File1000000 (writer SHAPE_1)
    LINE -> File100 (writer SHAPE_1)
    ARC -> File100 (writer SHAPE_1)
Note: The overall writer is set to fanout by cat value (over in the Navigator pane). This gives the subdirectories. Then the actual shapefiles are named according to the attribute we created on the features, and these draw their schemas from the attribute{} list on the features.
File1000000 (writer SHAPE_1)
File100 (writer SHAPE_1)
File10000 (writer SHAPE_1)

Bookmark: Build select clauses
Note: Build the part of the SQL necessary to select this attribute into this shapefile, either by wildcard, value, or values set
